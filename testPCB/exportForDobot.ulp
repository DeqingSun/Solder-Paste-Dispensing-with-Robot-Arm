#usage "<b>Gerenate solder paste file for dobot</b>\n"
       "<p>"
       "Generates files for smds on the top"
       "<p>"
       "RUN exportForDobot"
       "<p>"
       "<author>Author: Deqing Sun</author>"

//reference: https://github.com/plusea/EAGLE/blob/master/ulp/mountsmd.ulp
//http://web.mit.edu/xavid/arch/i386_rhel4/help/index.htm

if (board){
  board(B) {
  
    // Get filename
    string fileName = dlgFileSave("Save File", filesetext(B.name, ".csv"), "*.csv");
    //string fileName = "/Users/sundeqing/Desktop/tiny85Digispark0805.csv";
    if (fileName == "") exit(0);  
    output(fileName) { //outputfile # default in eagle app path
      printf("Part,Package,SMD_PAD,PadName,PadX,PadY,PadAngle,PadSizeX,PadsizeY\n");
      B.layers(L){
        if (L.name == "Dimension"){
          //printf("Layer %3d %s\n", L.number, L.name);
        }
      }
      B.elements(E){
        //elements are components. Their XY are reference points, which may not be useful. We will calculate XY with pads positions.
            //printf("Element: %s, (%f %f), Package=%s\n", E.name, u2mm(E.x), u2mm(E.y), E.package.name);
            string partName = E.name;
            string packageName = E.package.name;
            UL_PACKAGE PAC = E.package;
            {
              //printf("Package: %s\n", PAC.name);
              PAC.contacts(C) {
                if (C.pad){
                  string padName = C.name;
                  real padCenterX = u2mm(C.pad.x);
                  real padCenterY = u2mm(C.pad.y);
                  printf("%s,%s,%s,%s,%f,%f,,,\n", partName,packageName,"PAD", padName, padCenterX, padCenterY);
                }else if (C.smd){
                  string smdName = C.name;
                  real smdCenterX = u2mm(C.smd.x);
                  real smdCenterY = u2mm(C.smd.y);
                  real smdAngle = C.smd.angle;
                  real creamSizeX = u2mm(C.smd.dx[LAYER_TCREAM]);
                  real creamSizeY = u2mm(C.smd.dy[LAYER_TCREAM]);
                  printf("%s,%s,%s,%s,%f,%f,%f,%f,%f\n", partName,packageName,"SMD", smdName, smdCenterX, smdCenterY,smdAngle,creamSizeX,creamSizeY);
                }
                
                   
              }
            }  
      }
      
      int x1=mm2u(1000);
      int x2=mm2u(-1000);
      int y1=mm2u(1000);
      int y2=mm2u(-1000);
      B.wires(W) {
        if (W.layer == LAYER_DIMENSION){
          if (W.x1<x1) x1=W.x1;
          if (W.x2<x1) x1=W.x2;
          if (W.x1>x2) x2=W.x1;
          if (W.x2>x2) x2=W.x2;          
          if (W.y1<y1) y1=W.y1;
          if (W.y2<y1) y1=W.y2;
          if (W.y1>y2) y2=W.y1;
          if (W.y2>y2) y2=W.y2;         
        }
      }
      real cornerX1 = u2mm(x1);
      real cornerY1 = u2mm(y1);
      printf("%s,%s,%s,%s,%f,%f,,,\n", "CORNER LL","","", "", cornerX1, cornerY1);
      real cornerX2 = u2mm(x2);
      real cornerY2 = u2mm(y2);
      printf("%s,%s,%s,%s,%f,%f,,,\n", "CORNER UR","","", "", cornerX2, cornerY2);
      
      

    }   
  }

}else{
  dlgMessageBox("\n    Start this ULP in a Board    \n");
  exit(0);
}
